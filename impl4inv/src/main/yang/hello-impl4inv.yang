module hello-impl4inv {
    yang-version 1;
    namespace "urn:opendaylight:params:xml:ns:yang:hello:impl4inv";
    prefix "hello-impl4inv";

    import config { prefix config; revision-date 2013-04-05; }
    import opendaylight-md-sal-binding { prefix md-sal-binding; revision-date 2013-10-28;}

    description
        "Service definition for hello project";

    revision "2014-12-10" {
        description
            "Initial revision";
    }

    identity hello4inv {
        base config:module-type;
        config:java-name-prefix Hello4inv;
    }

    augment "/config:modules/config:module/config:configuration" {
        case hello4inv {
            when "/config:modules/config:module/config:type = 'hello4inv'";
            container broker {
                uses config:service-ref {
                    refine type {
                        mandatory true;
                        config:required-identity md-sal-binding:binding-broker-osgi-registry;
                    }
                }
            }
        }
    }
}
