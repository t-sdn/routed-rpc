module otn-general-types {
    yang-version 1;
    namespace "urn:etri:params:xml:ns:yang:otn-general-types";
    prefix "otypes";
    
   import ietf-inet-types {prefix inet; revision-date "2010-09-24";}
   import yang-ext {prefix ext; revision-date "2013-07-09";}


    revision "2015-01-05" {
        description "Initial revision of otn general types";
    }

    typedef otn-tunnel-rate-type {
        type enumeration {
            enum odu0;
            enum odu1;  
            enum odu2;
            enum odu3;
            enum odu4; 
            enum odu-flex;         
        }
    }
    typedef otn-switching-rate-type {
        type enumeration {
            enum odu0;
            enum odu1;  
            enum odu2;
            enum odu3;
            enum odu4; 
            enum odu-flex;         
        }
    }
    grouping otn-tunnel-bandwidth {

       leaf rate-type {
	            type otn-tunnel-rate-type;
	        }
	   leaf multiple-rate {
			type union {
				type uint32;
				type string;
			}
	   }
	}
    grouping otn-tunnel-xc-bandwidth {
        leaf rate-type {
            type otn-switching-rate-type;
        }
        leaf multiple-rate {
   			type union {
				type uint32;
				type string;
			}
        }
    }
 

}
