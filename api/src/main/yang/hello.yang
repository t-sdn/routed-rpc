module hello {
    yang-version 1;
    namespace "urn:opendaylight:params:xml:ns:yang:hello";
    prefix "hello";

    revision "2015-01-05" {
        description "Initial revision of hello model";
    }
    
    rpc hello-world {
    	input {
    		leaf strin {
    			type string;
    		}
    	}
    	output {
    		leaf strout {
    			type string;
    		}
    	}
    }
    
    rpc hello-world-read {
    	input {
    		leaf strin {
    			type string;
    		}
    	}
    	output {
    		leaf strout {
    			type string;
    		}
    	}
    }
    
    rpc hello-world-write {
    	input {
    		leaf strin {
    			type string;
    		}
    	}
    	output {
    		leaf strout {
    			type string;
    		}
    	}
    }
    
    notification multipleOfFive {
    }
    
    container helloWorld {
    	leaf counter {
    		type uint32;
    		config true;
    		default 100;
    	}
    	
    	leaf value {
    		type string;
    		config false;
    		mandatory false;
    	}
    }
}
