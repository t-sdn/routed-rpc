module tsdn-node {
    yang-version 1;
    namespace "urn:etri:params:xml:ns:yang:tsdn-node";
    prefix "tnode";
    
   import ietf-inet-types {prefix inet; revision-date "2010-09-24";}
//   import yang-ext {prefix ext; revision-date "2013-07-09";}
 
    revision "2015-01-05" {
        description "Initial revision of node model";
    }
    
    typedef node-id {
        type inet:uri;
        description "Identifier for a particular node";
    } 

    typedef node-ref {
        type instance-identifier;
        description "A reference that points to an nodes/node in the data tree.";
    }
    
    identity node-context {
        description "A node-context is a classifier for node elements which allows an RPC to provide a service on behalf of a particular element in the data tree.";
    }    
    
   typedef node-role {
        type enumeration {
            enum uni-source;
            enum uni-sink;
            enum bi-edge;
            enum uni-transit;
            enum bi-transit;            
        }
    }
    
    typedef node-type {
        type enumeration {
            enum otn;
            enum sdh;
            enum ptn;
            enum mpls-tp;
            enum roadm;
            enum all;
        }
    }
    typedef node-status {
        type enumeration {
            enum normal;
            enum unknown;
            enum broken;
            enum interrupted;              
        }
    }
    
    grouping common-node{
        leaf name {
            type string;
        }
        leaf node-type {
            type node-type;
        }        
        leaf ip-address {
            type inet:ip-address;
        }
        leaf manufacturer {
            type string;
        }
        leaf hardware {
            type string;
        }
        leaf software {
            type string;
        }
        leaf serial-number {
            type string;
        }
        leaf node-status {
            type node-status;
        }
    }
}
