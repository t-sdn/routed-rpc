module tsdn-tunnel {
    yang-version 1;
    namespace "urn:etri:params:xml:ns:yang:tsdn-tunnel";
    prefix "ttunnel";
    
    import ietf-inet-types {prefix inet; revision-date "2010-09-24";}
//   import yang-ext {prefix ext; revision-date "2013-07-09";}
 
 
    revision "2015-01-05" {
        description "Initial revision of tunnel model";
    }

    typedef tunnel-id {
        type inet:uri;
        description "Identifier for a particular tunnel";
    }
    typedef tunnel-ref {
        type instance-identifier;
        description "A reference that points to an nodes/node/{node_id}/tunnel in the data tree.";
    }

    typedef tunnel-status {
        type enumeration {
            enum normal;
            enum unknown;
            enum broken;
            enum adding;
            enum deleting;
            enum interrupted;            
        }
    }
    typedef tunnel-stage {
        type enumeration {
            enum 0;
            enum 1;
            enum 2;
            enum 3;
        }
    }
 
    typedef tunnel-type {
        type enumeration {
            enum packet;
            enum otn;  
            enum sdh;
            enum wdm;
            enum all;         
        }
    }
    
    grouping common-tunnel {
    	leaf name {
            type string;
        }
        leaf tunnel-type {
            type tunnel-type;
        }
    	leaf tunnel-status {
            type tunnel-status;
        }
    }
}
