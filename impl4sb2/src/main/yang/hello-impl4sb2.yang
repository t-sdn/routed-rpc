module hello-impl4sb2 {
    yang-version 1;
    namespace "urn:opendaylight:params:xml:ns:yang:hello:impl4sb2";
    prefix "hello-impl4sb2";

    import config { prefix config; revision-date 2013-04-05; }
    import opendaylight-md-sal-binding { prefix md-sal-binding; revision-date 2013-10-28;}
    import rpc-context { prefix rpcx; revision-date 2013-06-17; }

    description
        "Service definition for hello project";

    revision "2014-12-10" {
        description
            "Initial revision";
    }

    identity hello4sb2 {
        base config:module-type;
        config:java-name-prefix Hello4sb2;
    }

    augment "/config:modules/config:module/config:configuration" {
        case hello4sb2 {
            when "/config:modules/config:module/config:type = 'hello4sb2'";
            container broker {
                uses config:service-ref {
                    refine type {
                        mandatory true;
                        config:required-identity md-sal-binding:binding-broker-osgi-registry;
                    }
                }
            }
        }
    }
    
    augment "/config:modules/config:module/config:state" {
    	case hello4sb2 {
    		when "/config:modules/config:module/config:type = 'hello4sb2'";
    		
    		rpcx:rpc-context-instance "update-sb-node-rpc";
    	}
    }
    
    identity update-sb-node-rpc;
    
    rpc update-sb2-node {
    	description
    		"JMX call to update the node.";
    		
    	input {
    		uses rpcx:rpc-context-ref {
    			refine context-instance {
    				rpcx:rpc-context-instance update-sb-node-rpc;
    			}
    		}
    		leaf id {
    			type string;
    		}
    	}
    }
}
